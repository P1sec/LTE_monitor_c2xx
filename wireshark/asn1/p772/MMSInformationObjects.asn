-- $Id: MMSInformationObjects.asn 31474 2010-01-09 20:52:47Z stig $
MMSInformationObjects {iso(1) identified-organization(3) nato(26) stanags(0)
  mmhs(4406) object-identifiers(0) module(0) mms(1)} DEFINITIONS IMPLICIT TAGS
::=
BEGIN

-- Prologue
-- Exports Everything
IMPORTS
  -- IPM Information Object
  Body, CommonFields, Heading, NonReceiptFields, OtherNotificationTypeFields,
    ReceiptFields, IPM, IPN
    --=
    FROM IPMSInformationObjects {joint-iso-ccitt mhs-motis(6) ipms(1)
      modules(0) information-objects(2)}
  -- MTS abstract service
  ORName
    --=
    FROM MTSAbstractService {joint-iso-ccitt mhs-motis(6) mts(3) modules(0)
      mts-abstract-service(1)};

-- Information Object
--InformationObject ::= CHOICE {mm  [0]  MM,
--                              mn  [1]  MN}

-- We use IPM and IPN here because asn2wrs is unable to fetch
-- COMPONENTS OF CommonFields from IPMSInformationObjects.asn (x420).
InformationObject ::= CHOICE {mm  [0]  IPM,
                              mn  [1]  IPN}

-- MM (Military Message)
MM ::= SEQUENCE {mmheading  Heading,
                 mmbody     Body}

-- The mandatory support on the IPMIdentifier components is more important
-- in MMS than in IPMS. The user component, ORName of the originating UA is
-- mandatory. Local IPMIdentifier is made up of 2 concatenated string
-- separated by a space both generated by the originating UA, a serial
-- number and the filing time (the time the message generation is finished)
-- in UTC time format. The minimum length of 15 is because both a date/time
-- stamp in UTC format including seconds and a serial number, plus the space
-- delimiter are mandatory. The smallest acceptable UTC date/time stamp
-- is 13 (ddmmyyhhmmssZ).
-- MN (Military Notification receipt/non receipt / other notification types)
MN ::= SET {
  COMPONENTS OF CommonFields,
  choice
    [0]  CHOICE {mn-non-receipt-fields              [0]  NonReceiptFields,
                 mn-receipt-fields                  [1]  ReceiptFields,
                 mn-other-notification-type-fields
                   [2]  OtherNotificationTypeFields}}

MRN ::= MN -- with MN-receipt-fields chosen

MNRN ::= MN -- with MN-non-receipt-fields chosen

MON ::= MN -- with MN-other-notification-type-fields chosen

-- All military specific body parts are defined as extended body parts. 
-- The military specific body parts are defined in Annex A 
-- of this part of the MBS.
END -- of MMS InformationObjects
