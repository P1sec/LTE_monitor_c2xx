--
-- $Id: Basic-Service-Elements.asn 47709 2013-02-17 19:07:27Z guy $
--
-- EN 300 196-1 Ver. 1.3.2
--
Basic-Service-Elements {itu-t identified-organization etsi(0) 196 basic-service-elements(8)}

DEFINITIONS EXPLICIT TAGS ::=

BEGIN

EXPORTS                 BasicService;

BasicService            ::= ENUMERATED {
                                allServices (0),
                                speech (1),
                                unrestrictedDigitalInformation (2),
                                audio3k1Hz (3),
                                unrestrictedDigitalInformationWithTonesAndAnnouncements (4),
                                multirate(5),
                                telephony3k1Hz (32),
                                teletex (33),
                                telefaxGroup4Class1 (34),
                                videotexSyntaxBased (35),
                                videotelephony (36),
                                telefaxGroup2-3 (37),
                                telephony7kHz (38),
                                euroFileTransfer (39),
                                fileTransferAndAccessManagement (40),
                                videoconference (41),
                                audioGraphicConference (42)
                            }

END -- of Basic-Service-Elements
