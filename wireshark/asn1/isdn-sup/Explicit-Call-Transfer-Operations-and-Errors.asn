-- $Id: Explicit-Call-Transfer-Operations-and-Errors.asn 47746 2013-02-19 18:44:06Z etxrab $
--
-- EN 300 369-1 V1.2.4 (1998-10)
--
Explicit-Call-Transfer-Operations-and-Errors {ccitt identified-organization etsi(0) 369
version(2) operations-and-errors(1)}

DEFINITIONS ::=

 
BEGIN

 
  EXPORTS
      ectLinkIdRequest,
      ectExecute,
      requestSubaddress,
      subaddressTransfer,
      explicitEctExecute,
      linkIdNotAssignedByNetwork,
      ectLoopTest,
      ectInform;

 
  IMPORTS
      OPERATION,
      ERROR
    FROM Remote-Operations-Information-Objects
    {joint-iso-itu-t remote-operations (4) notation (0)} 

 
      notAvailable,
      notSubscribed,
      resourceUnavailable,
      supplementaryServiceInteractionNotAllowed,
      invalidCallState
    FROM General-Errors
    {itu-t(0) identified-organization(4) etsi (0) 196 general-errors (2)}

 
      PartySubaddress,
      PresentedNumberUnscreened
    FROM Addressing-Data-Elements
    {itu-t(0) identified-organization(4) etsi (0) 196 addressing-data-elements (6)};

 
  ectExecute OPERATION::=
    {
      ERRORS {
        notAvailable |
        notSubscribed |
        invalidCallState |
        supplementaryServiceInteractionNotAllowed }  
        
      CODE local:6        
    }

  ectInform OPERATION::=
    {
      ARGUMENT SEQUENCE {
          en ENUMERATED {
            alerting (0),
            active   (1) },
          redirectionNumber    PresentedNumberUnscreened OPTIONAL }   
          
      CODE global:{eCTOID ectInform-operation (5)}           
    }

  ectLinkIdRequest OPERATION::=
    {  
      RESULT EctLinkIdRequestRes
      ERRORS {
        resourceUnavailable }  
        
      CODE global:{eCTOID ectLinkIdRequest-operation (4)}      
    }

 EctLinkIdRequestRes ::= LinkId

 ectLoopTest OPERATION::=
    {
      ARGUMENT
          CallTransferIdentity

 
      RESULT
        LoopResult

 
      ERRORS {
        notAvailable }   
        
      CODE global:{eCTOID ectLoopTest-operation (6)}       
    }


  explicitEctExecute OPERATION::=
    {  
      ARGUMENT
        LinkId        
        
      ERRORS {
        notAvailable |
        notSubscribed |
        invalidCallState |
        supplementaryServiceInteractionNotAllowed |    
        linkIdNotAssignedByNetwork }
        
      CODE global:{eCTOID explicitEctExecute-operation (1)}          
    }

 
  requestSubaddress OPERATION::=
    {
      CODE global:{eCTOID requestSubAddress-operation (2)}
    }      

 
  subaddressTransfer OPERATION::=
     {
      ARGUMENT  PartySubaddress   
      
      CODE global:{eCTOID subaddressTransfer-operation (3)}     
     }

  CallTransferIdentity ::= INTEGER (-128..127) 
  LinkId ::= INTEGER (-32768..32767)

  LoopResult ::=
      ENUMERATED {
        insufficientInformation (0),
        noLoopExists            (1),
        simultaneousTransfer    (2) }

 
  eCTOID OBJECT IDENTIFIER ::= {itu-t(0) identified-organization(4) etsi (0) 369
                                operation-and-errors (1)}

 
  linkIdNotAssignedByNetwork ERROR ::= {CODE global:{eCTOID linkIdNotAssignedByNetwork-error (21)}}


--  ectExecute EctExecute ::= localValue 6
	explicitEctExecute			ExplicitEctExecute			::=	globalValue {eCTOID explicitEctExecute-operation(1)}
	requestSubaddress			RequestSubaddress			::=	globalValue {eCTOID requestSubaddress-operation (2)}
	subaddressTransfer			SubaddressTransfer			::=	globalValue {eCTOID subaddressTransfer-operation(3)}
	ectLinkIdRequest			EctLinkIdRequest			::=	globalValue {eCTOID ectLinkIdRequest-operation (4)}
	ectInform					EctInform					::= globalValue {eCTOID ectInform-operation (5)}
	ectLoopTest					EctLoopTest					::= globalValue {eCTOID ectLoopTest-operation (6)}
	linkIdNotAssignedByNetwork	LinkIdNotAssignedByNetwork	::= globalValue {eCTOID 	linkIdNotAssignedByNetwork-error(21)}
END --Explicit-Call-Transfer-Operations-And-Errors
