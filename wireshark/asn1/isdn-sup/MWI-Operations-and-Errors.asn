-- $Id: MWI-Operations-and-Errors.asn 47746 2013-02-19 18:44:06Z etxrab $
--
-- prETS 300 745-1
--
MWI-Operations-and-Errors {itu-t(0) identified-organization(4) etsi(0) 745 operations-and-errors(1)}

DEFINITIONS EXPLICIT TAGS ::=

BEGIN

EXPORTS		MWIActivate,
			MWIDeactivate,
			MWIIndicate,
			InvalidReceivingUserNr,
			ReceivingUserNotSubscribed,
			ControllingUserNotRegistered,
			MaxNumOfControllingUsersReached,
			MaxNumOfActiveInstancesReached
;
IMPORTS		OPERATION,
			ERROR
			FROM Remote-Operations-Information-Objects 
    {joint-iso-itu-t (2) remote-operations (4) informationObjects(5) version1(0)}

			notSubscribed,
			supplementaryServiceInteractionNotAllowed,
			resourceUnavailable,
			invalidServedUserNr
			FROM General-Errors
				{itu-t(0) identified-organization(4) etsi(0) 196 general-errors(2)}

			BasicService
			From Basic-Service-Elements
				{itu-t(0) identified-organization(4) etsi(0) 196 basic-service-elements(8)}

			PartyNumber
			FROM Addressing-Data-Element
				{itu-t(0) identified-organization(4) etsi(0) 196 addressing-data-elements(6)}
;

  mWIActivate OPERATION::=
    {  
        ARGUMENT SEQUENCE {
          receivingUserNr             PartyNumber,
          basicService                BasicService,
          controllingUserNr           [1] PartyNumber OPTIONAL,
          numberOfMessages            [2] MessageCounter OPTIONAL,
          controllingUserProvidedNr   [3] PartyNumber OPTIONAL,
          time                        [4] GeneralizedTime OPTIONAL,
          messageId                   [5] MessageID OPTIONAL,
          mode                        [6] InvocationMode OPTIONAL }
 
        ERRORS {
          notSubscribed |
          supplementaryServiceInteractionNotAllowed |
          resourceUnavailable |
          invalidReceivingUserNr |
          invalidServedUserNr |
          receivingUserNotSubscribed |
          controllingUserNotRegistered |
          indicationNotDelivered |
          maxNumOfControllingUsersReached |
          maxNumOfActiveInstancesReached }     
          
        CODE global:{mWIOID 1}       
    }
-- End of MWIActivate operation definition

  mWIDeactivate OPERATION::=
    {  
        ARGUMENT SEQUENCE {
          receivingUserNr     PartyNumber,
          basicService        BasicService,
          controllingUserNr   PartyNumber OPTIONAL,
          mode                InvocationMode OPTIONAL }
 
        ERRORS {
          notSubscribed |
          supplementaryServiceInteractionNotAllowed |
          resourceUnavailable |
          invalidReceivingUserNr |
          invalidServedUserNr |
          receivingUserNotSubscribed |
          controllingUserNotRegistered |
          indicationNotDelivered }    
          
        CODE global:{mWIOID 2}         
    }
-- End of MWIDeactivate operation definition

  mWIIndicate OPERATION::=
    {  
        ARGUMENT SEQUENCE {
          controllingUserNr           [1] PartyNumber OPTIONAL,
          basicService                [2] BasicService OPTIONAL,
          numberOfMessages            [3] MessageCounter OPTIONAL,
          controllingUserProvidedNr   [4] PartyNumber OPTIONAL,
          time                        [5] GeneralizedTime OPTIONAL,
          messageId                   [6] MessageID OPTIONAL }  
          
        CODE global:{mWIOID 3}            
    }
-- End of MWIIndicate operation definition

  invalidReceivingUserNr           ERROR ::= {CODE global:{mWIOID 10}}   
  receivingUserNotSubscribed       ERROR ::= {CODE global:{mWIOID 11}}
  controllingUserNotRegistered     ERROR ::= {CODE global:{mWIOID 12}}
  indicationNotDelivered           ERROR ::= {CODE global:{mWIOID 13}}
  maxNumOfControllingUsersReached  ERROR ::= {CODE global:{mWIOID 14}}
  maxNumOfActiveInstancesReached   ERROR ::= {CODE global:{mWIOID 15}}

MessageCounter					::= INTEGER (0..65535)

GeneralizedTime					::= [UNIVERSAL 24] IMPLICIT VisibleString

MessageID						::= SEQUENCE {
										messageRef	MessageRef,
										status		MessageStatus}

MessageRef						::= INTEGER (0..65535)

MessageStatus					::= ENUMERATED (
										addedMessage	(0),
										removedMessage	(1)}

InvocationMode					::= ENUMERATED (
										deferred	(0),
										immediate	(1),
										combined	(2))

mWIOID OBJECT IDENTIFIER 		::= {itu-t(0) identified-organization(4) etsi(0) 745
								     operations-and-errors(1)}

mWIActivate						MWIActivate						::= globalValue {mWIOID 1}
mWIDeactivate					MWIDeactivate					::= globalValue {mWIOID 2}
mWIIndicate						MWIIndicate						::= globalValue {mWIOID 3}

invalidReceivingUserNr			InvalidReceivingUserNr			::= globalValue {mWIOID 10}
receivingUserNotSubscribed		ReceivingUserNotSubscribed		::= globalValue {mWIOID 11}
controllingUserNotRegistered	ControllingUserNotRegistered	::= globalValue {mWIOID 12}
indicationNotDelivered			IndicationNotDelivered			::= globalValue {mWIOID 13}
maxNumOfControllingUsersReached	MaxNumOfControllingUsersReached	::= globalValue {mWIOID 14}
maxNumOfActiveInstancesReached	MaxNumOfActiveInstancesReached	::= globalValue	{mWIOID 15}

END -- MWI-Operations-and-Errors
