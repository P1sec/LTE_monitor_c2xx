--
-- $Id: Three-Party-Operations.asn 47746 2013-02-19 18:44:06Z etxrab $
--
-- EN 300 188-1 V1.2.4 (1998-06)
--
Three-Party-Operations {ccitt identified-organization etsi (0) 188 operations-and-types (1)}

DEFINITIONS EXPLICIT TAGS ::=

BEGIN

EXPORTS
  begin3PTY,
  end3PTY;
  
IMPORTS
    OPERATION
  FROM Remote-Operations-Information-Objects
  {joint-iso-itu-t remote-operations (4) notation (0)}

 
    notSubscribed,
    notAvailable,
    invalidCallState,
    resourceUnavailable,
    supplementaryServiceInteractionNotAllowed
  FROM General-Errors
  {itu-t identified-organization etsi (0) 196 general-errors (2)};
  
  begin3PTY OPERATION ::=
    {
      ERRORS {
        notSubscribed |
        notAvailable |
        invalidCallState |
        resourceUnavailable |
        supplementaryServiceInteractionNotAllowed }
        -- ETS 300 188, aug 1993 does not provide procedures for the generation
        -- of the error 'notAvailable'
        
      CODE local:4          
    }
    
 
  end3PTY OPERATION ::=
    {
      ERRORS {
        invalidCallState }
        
      CODE local:5  
    }


 
END
