--
-- $Id: General-Errors.asn 47738 2013-02-18 19:34:04Z etxrab $
--
-- EN 300 196-1 Ver. 1.3.2
--

General-Errors {itu-t identified-organization etsi(0) 196 general-errors(2)}

DEFINITIONS EXPLICIT TAGS ::=

BEGIN

EXPORTS                 notSubscribed, notAvailable, notImplemented, invalidServedUserNr,
                        invalidCallState, basicServiceNotProvided, notIncomingCall,
                        supplementaryServiceInteractionNotAllowed, resourceUnavailable;

IMPORTS                 ERROR
                        FROM Remote-Operations-Information-Objects 
    {joint-iso-itu-t (2) remote-operations (4) informationObjects(5) version1(0)};

notSubscribed  ERROR ::= { CODE  local: 0}


        -- The requested service or function has not been subscribed for the basic service, and
        -- optionally the served user's ISDN number, included in the activation invoke component.
        -- Alternatively the basic service may not have been subscribed.


notAvailable  ERROR ::= { CODE  local: 3}

        -- The requested supplementary service or function is not available for the basic service,
        -- and optionally the served user's ISDN number (e.g. temporary fault).

notImplemented  ERROR ::= { CODE  local: 4}

        -- The supplementary service or function requested is not implemented for the basic
        -- service, and optionally the served user's ISDN number (e.g. service not provided).

invalidServedUserNr  ERROR ::= { CODE  local: 6}

        -- The served user's number provided is not a valid number.

invalidCallState  ERROR ::= { CODE  local: 7}

        -- The supplementary service or function cannot be requested in the current basic call state
        -- or auxiliary state.

basicServiceNotProvided  ERROR ::= { CODE  local: 8}

        -- The served user has not subscribed to the basic service (bearer and/or teleservice) for
        -- which the supplementary service or function was requested.

notIncomingCall  ERROR ::= { CODE  local: 9}

        -- The supplementary service or function was not requested for an incoming call.

supplementaryServiceInteractionNotAllowed  ERROR ::= { CODE  local: 10}

        -- The performance of the requested supplementary service or function is prohibited
        -- by another supplementary service or function.

resourceUnavailable  ERROR ::= { CODE  local: 11}

        -- The resources required to perform adequately the requested supplementary service or
        -- function are not available.

END -- of General-Errors
