-- $Id: IN-errortypes.asn 32061 2010-03-01 09:30:45Z etxrab $
-- Module IN-errortypes (Q.1248.1:07/2001)
IN-errortypes {itu-t recommendation q 1248 modules(1) in-errortypes(2)
  version1(0)} DEFINITIONS IMPLICIT TAGS ::=
BEGIN

IMPORTS
  ros-InformationObjects, common-datatypes, errorcodes, sdf-sdf-Operations,
    scf-scf-classes, ds-UsefulDefinitions, spkmGssTokens, tc-Messages
    FROM IN-object-identifiers {itu-t recommendation q 1248 modules(1)
      in-object-identifiers(0) version1(0)}
  directoryAbstractService, distributedOperations, enhancedSecurity
    FROM UsefulDefinitions ds-UsefulDefinitions
  OPTIONALLY-PROTECTED{}, dirqop
    FROM EnhancedSecurity enhancedSecurity
  CommonResults, ServiceProblem, SecurityProblem, SecurityParameters, Versions
    FROM DirectoryAbstractService directoryAbstractService
  scfqop
    FROM IN-SCF-SCF-Classes scf-scf-classes
  AccessPointInformation
    FROM DistributedOperations distributedOperations
  SPKM-ERROR
    FROM SpkmGssTokens spkmGssTokens
  ERROR
    FROM Remote-Operations-Information-Objects ros-InformationObjects
  InvokeID, UnavailableNetworkResource
    FROM IN-common-datatypes common-datatypes
  errcode-canceled, errcode-cancelFailed, errcode-chainingRefused,
    errcode-eTCFailed, errcode-executionError, errcode-improperCallerResponse,
    errcode-missingCustomerRecord, errcode-missingParameter,
    errcode-parameterOutOfRange, errcode-requestedInfoError,
    errcode-scfTaskRefused, errcode-scfReferral, errcode-systemFailure,
    errcode-taskRefused, errcode-unavailableResource,
    errcode-unexpectedComponentSequence, errcode-unexpectedDataValue,
    errcode-unexpectedParameter, errcode-unknownLegID, errcode-unknownResource
    FROM IN-errorcodes errorcodes;

-- TYPE DEFINITION FOR    IN CS4    ERRORS FOLLOWS
canceled ERROR ::= {CODE  errcode-canceled
}

-- The operation has been cancelled.
cancelFailed ERROR ::= {
  PARAMETER
    SEQUENCE {problem
                [0]  ENUMERATED {unknownOperation(0), tooLate(1),
                                 operationNotCancellable(2)},
              operation  [1]  InvokeID}
  CODE       errcode-cancelFailed
}

-- The operation failed to be cancelled.
chainingRefused ERROR ::= {CODE  errcode-chainingRefused
}

eTCFailed ERROR ::= {CODE  errcode-eTCFailed
}

-- The establish temporary connection failed.
-- WS:Duplicates error-code
--executionError ERROR ::= {
--  PARAMETER OPTIONALLY-PROTECTED
--    {SET {problem  [0] EXPLICIT ExecutionProblem,
--          COMPONENTS OF CommonResults}
--     dirqop.&dirErrors-QOP},
--  CODE                            errcode-executionError
--}

-- The executionError is returned by an Execute operation in the case of the operation is not completing.
--ExecutionProblem ::= INTEGER {missingInputValues(1), executionFailure(2)
--}

-- The executeProblem identifies the cause of the execute operation failure:
-- missingInputValues is returned in the input-values field contains the wrong input 
-- information for the method being executed.
-- executionFailure is returned when the method fails to complete correctly. This is caused by
-- .the failure of one of the DAP operations contained within the method.
improperCallerResponse ERROR ::= {CODE  errcode-improperCallerResponse
}

-- The caller response was not as expected.
missingCustomerRecord ERROR ::= {CODE  errcode-missingCustomerRecord
}

-- The Service Logic Program could not be found in the SCF.
missingParameter ERROR ::= {CODE  errcode-missingParameter
}

-- An expected optional parameter was not received.
parameterOutOfRange ERROR ::= {CODE  errcode-parameterOutOfRange
}

-- The parameter was not as expected (e.g. missing or out of range).
requestedInfoError ERROR ::= {
  PARAMETER
    ENUMERATED {unknownRequestedInfo(1), requestedInfoNotAvailable(2)
                                         -- other values FFS
                                         }
  CODE       errcode-requestedInfoError
}

-- The requested information cannot be found.
-- WS:CODE missing comment it out
--scfBindFailure ERROR ::= {PARAMETER  FailureReason
--}

--FailureReason ::= CHOICE {
--  systemFailure   [0]  UnavailableNetworkResource,
--  scfTaskRefused  [1]  ScfTaskRefusedParameter,
--  securityError
--    [2]  SET {problem   [0]  SecurityProblem,
--              spkmInfo  [1]  SPKM-ERROR}
--}

scfTaskRefused ERROR ::= {
  PARAMETER  ScfTaskRefusedParameter
  CODE       errcode-scfTaskRefused
}

ScfTaskRefusedParameter ::=
--  OPTIONALLY-PROTECTED
    SEQUENCE {reason
                 ENUMERATED {generic(0), unobtainable(1), congestion(2)
                                                          --other values FFS
                                                          },
               securityParameters  [1]  SecurityParameters OPTIONAL
    }--, scfqop.&scfErrorsQOP}

scfReferral ERROR ::= {
  PARAMETER  ReferralParameter
  CODE       errcode-scfReferral
}

ReferralParameter ::=
--  OPTIONALLY-PROTECTED
    SEQUENCE {tryhere             [0]  AccessPointInformation,
               securityParameters  [1]  SecurityParameters OPTIONAL
    }--, scfqop.&scfErrorsQOP}

systemFailure ERROR ::= {
  PARAMETER  UnavailableNetworkResource
  CODE       errcode-systemFailure
}

-- The operation could not be completed due to e.g. a system failure at the serving physical entity, the 
-- unavailability of the required resource or due to screening.
taskRefused ERROR ::= {
  PARAMETER
    ENUMERATED {generic(0), unobtainable(1), congestion(2)
                                             --other values FFS
                                             }
  CODE       errcode-taskRefused
}

-- An entity normally capable of the task requested cannot or chooses not to perform the task at this 
-- time. This includes error situations like congestion and unobtainable address as used in e.g. the 
-- connect operation.
-- WS:CODE missing comment it out
-- tfcBindError ERROR ::= {
--   PARAMETER
--     SET {versions  [0]  Versions DEFAULT {v1},
--          error
--            CHOICE {serviceError   [1]  ServiceProblem,
--                    securityError  [2]  SecurityProblem}}
-- }

unavailableResource ERROR ::= {CODE  errcode-unavailableResource
}

-- A requested resource is not available at the serving entity.
unexpectedComponentSequence ERROR ::= {
  CODE  errcode-unexpectedComponentSequence
}

-- An incorrect sequence of Components was received (e.g. "DisconnectForwardConnection" 
-- followed by "PlayAnnouncement").
unexpectedDataValue ERROR ::= {CODE  errcode-unexpectedDataValue
}

-- The data value was not as expected (e.g. routing number expected but billing number received)
unexpectedParameter ERROR ::= {CODE  errcode-unexpectedParameter
}

-- A parameter received was not expected.
unknownLegID ERROR ::= {CODE  errcode-unknownLegID
}

-- Leg not known to the SSF.
unknownResource ERROR ::= {CODE  errcode-unknownResource
}

-- Resource whose status is being requested is not known to the serving entity.
END

-- Generated by Asnp, the ASN.1 pretty-printer of France Telecom R&D
