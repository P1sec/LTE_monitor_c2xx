-- SBC-AP-CommonDataTypes.asn
--
-- Taken from 3GPP TS 29.168 V9.3.0 (2010-12)
-- http://www.3gpp.org/ftp/Specs/archive/29_series/29.168/29168-930.zip
--
-- 4.4.6	Common Definitions
--
-- $Id: SBC-AP-CommonDataTypes.asn 39756 2011-11-08 17:17:05Z etxrab $??
--

-- **************************************************************
--
-- Common definitions
--
-- **************************************************************

SBC-AP-CommonDataTypes {
itu-t (0) identified-organization (4) etsi (0) mobileDomain (0) 
eps-Access (21) modules (3) sbc-AP (3) version1 (1) sbc-AP-CommonDataTypes (3)}

DEFINITIONS AUTOMATIC TAGS ::= 

BEGIN

Criticality		::= ENUMERATED { reject, ignore, notify }

Presence		::= ENUMERATED { optional, conditional, mandatory }

ProcedureCode		::= INTEGER (0..255)

ProtocolExtensionID	::= INTEGER (0..65535)

ProtocolIE-ID		::= INTEGER (0..65535)

TriggeringMessage		::= ENUMERATED {initiating-message, successful-outcome, unsuccessful-outcome, outcome}

END
