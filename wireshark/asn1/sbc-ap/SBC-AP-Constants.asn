-- SBC-AP-Constants.asn
--
-- Taken from 3GPP TS 29.168 V9.3.0 (2010-12)
-- http://www.3gpp.org/ftp/Specs/archive/29_series/29.168/29168-930.zip
--
-- 4.4.7	Constant Definitions
--
-- $Id: SBC-AP-Constants.asn 39756 2011-11-08 17:17:05Z etxrab $??
--
-- **************************************************************
--
-- Constant definitions
--
-- **************************************************************

SBC-AP-Constants {
itu-t (0) identified-organization (4) etsi (0) mobileDomain (0) 
eps-Access (21) modules (3) sbc-AP (3) version1 (1) sbc-AP-Constants (4)}

DEFINITIONS AUTOMATIC TAGS ::= 

BEGIN

-- **************************************************************
--
-- Elementary Procedures
--
-- **************************************************************

id-Write-Replace-Warning 			INTEGER ::= 0 
id-Stop-Warning 					INTEGER ::= 1


-- **************************************************************
--
-- IEs
--
-- **************************************************************

id-Broadcast-Message-Content		INTEGER ::= 0
id-Cause 				INTEGER ::= 1
id-Criticality-Diagnostics	INTEGER ::=2
id-Data-Coding-Scheme 			INTEGER ::= 3
id-Failure-List 			INTEGER ::= 4
id-Message-Identifier 			INTEGER ::= 5
id-Number-of-Broadcasts-Completed-List 	INTEGER ::= 6
id-Number-of-Broadcasts-Requested 		INTEGER ::= 7
id-Radio-Resource-Loading-List 		INTEGER ::= 8
id-Recovery-Indication 			INTEGER ::= 9
id-Repetition-Period 			INTEGER ::= 10
id-Serial-Number 			INTEGER ::= 11
id-Service-Areas-List 			INTEGER ::= 12
id-TypeOfError					INTEGER ::= 13
id-List-of-TAIs					INTEGER ::= 14
id-Warning-Area-List 			INTEGER ::= 15
id-Warning-Message-Content		INTEGER ::= 16
id-Warning-Security-Information	INTEGER ::= 17
id-Warning-Type					INTEGER ::= 18 
id-Omc-Id 						INTEGER ::= 19 
id-Concurrent-Warning-Message-Indicator INTEGER ::= 20 
id-Extended-Repetition-Period	INTEGER ::= 21



-- **************************************************************
--
-- Extension constants
--
-- **************************************************************

-- **************************************************************
--
-- Lists
--
-- **************************************************************

maxNrOfErrors				INTEGER ::= 256 
maxnoofCellID				INTEGER	::= 65535
maxNrOfTAIs					INTEGER ::= 65535
maxnoofgencyEmerAreaID		INTEGER	::= 65535
maxnoofTAIforWarning		INTEGER ::= 65535

maxProtocolExtensions 			INTEGER ::= 65535
maxProtocolIEs				INTEGER ::= 65535
-- WS fix
maxnoofEmerAreaIDs			INTEGER ::= 65535
END
