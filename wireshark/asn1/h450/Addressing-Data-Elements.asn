-- Addressing-Data-Elements.asn
--
-- Taken from ITU ASN.1 database
-- http://www.itu.int/ITU-T/asn1/database/itu-t/h/h450.1/1998/Addressing-Data-Elements.asn
--
-- $Id: Addressing-Data-Elements.asn 22417 2007-07-30 08:01:59Z kukosa $
--

-- Module Addressing-Data-Elements (H.450.1:02/1998)
Addressing-Data-Elements {itu-t recommendation h 450 1 version1(0)
  addressing-data-elements(9)} DEFINITIONS AUTOMATIC TAGS ::=
BEGIN

IMPORTS
  AliasAddress, PartyNumber, PresentationIndicator, ScreeningIndicator
    FROM H323-MESSAGES; -- see H.225.0

PresentedAddressScreened ::= CHOICE {
  presentationAllowedAddress           AddressScreened,
  presentationRestricted               NULL,
  numberNotAvailableDueToInterworking  NULL,
  presentationRestrictedAddress        AddressScreened,
  ...
}

PresentedAddressUnscreened ::= CHOICE {
  presentationAllowedAddress           Address,
  presentationRestricted               NULL,
  numberNotAvailableDueToInterworking  NULL,
  presentationRestrictedAddress        Address,
  ...
}

PresentedNumberScreened ::= CHOICE {
  presentationAllowedAddress           NumberScreened,
  presentationRestricted               NULL,
  numberNotAvailableDueToInterworking  NULL,
  presentationRestrictedAddress        NumberScreened,
  ...
}

PresentedNumberUnscreened ::= CHOICE {
  presentationAllowedAddress           PartyNumber,
  presentationRestricted               NULL,
  numberNotAvailableDueToInterworking  NULL,
  presentationRestrictedAddress        PartyNumber,
  ...
}

AddressScreened ::= SEQUENCE {
  partyNumber         PartyNumber,
  screeningIndicator  ScreeningIndicator,
  partySubaddress     PartySubaddress OPTIONAL,
  ...
}

NumberScreened ::= SEQUENCE {
  partyNumber         PartyNumber,
  screeningIndicator  ScreeningIndicator,
  ...
}

Address ::= SEQUENCE {
  partyNumber      PartyNumber,
  partySubaddress  PartySubaddress OPTIONAL,
  ...
}

-- PartyNumber defined in Recommendation H.225.0
-- PublicPartyNumber defined in Recommendation H.225.0
-- PrivatePartyNumber defined in Recommendation H.225.0
-- NumberDigits defined in Recommendation H.225.0
-- PublicTypeOfNumber defined in Recommendation H.225.0
-- PrivateTypeOfNumber defined in Recommendation H.225.0
-- PresentationIndicator defined in Recommendation H.225.0 (v3 and beyond)
-- ScreeningIndicator defined in Recommendation H.225.0 (v3 and beyond)
EndpointAddress ::= SEQUENCE {
  destinationAddress                              SEQUENCE OF AliasAddress,
  -- multiple alias addresses may be used to address the same H.323 endpoint
  remoteExtensionAddress                          AliasAddress OPTIONAL,
  ...,
  destinationAddressPresentationIndicator
    PresentationIndicator OPTIONAL,
  -- Note 1, 2
  destinationAddressScreeningIndicator            ScreeningIndicator OPTIONAL,
  remoteExtensionAddressPresentationIndicator
    PresentationIndicator OPTIONAL,
  -- Note 1, 2
  remoteExtensionAddressScreeningIndicator        ScreeningIndicator OPTIONAL
}

-- Note 1: If this element is not available, presentation allowed shall be assumed.
-- Note 2: If an H.450 APDU that carries this element EndpointAddress also
-- contains an element PresentationAllowedIndicator, then the setting of the
-- element PresentationAllowedIndicator shall take precedence in case of
-- conflicting presentation information.
PartySubaddress ::= CHOICE {
  userSpecifiedSubaddress  UserSpecifiedSubaddress,
  -- not recommended.
  nsapSubaddress           NSAPSubaddress,
  -- according to Recommendation X.213. 
  ...
}

UserSpecifiedSubaddress ::= SEQUENCE {
  subaddressInformation  SubaddressInformation,
  oddCountIndicator      BOOLEAN OPTIONAL,
  -- used when the coding of subaddress is BCD
  ...
}

NSAPSubaddress ::= OCTET STRING(SIZE (1..20))

-- specified according to X.213. Some networks may
-- limit the subaddress value to some other length
-- e.g. 4 octets
SubaddressInformation ::= OCTET STRING(SIZE (1..20))

-- coded according to user requirements. Some networks 
-- may limit the subaddress value to some other length
-- e.g. 4 octets
PresentationAllowedIndicator ::= BOOLEAN

END -- of Addressing-Data-Elements

-- Generated by Asnp, the ASN.1 pretty-printer of France Telecom R&D
