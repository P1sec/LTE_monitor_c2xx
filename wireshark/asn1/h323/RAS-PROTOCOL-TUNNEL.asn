-- RAS-PROTOCOL-TUNNEL.asn
--
-- Taken from ITU ASN.1 database
-- http://www.itu.int/ITU-T/asn1/database/itu-t/h/h323/2006/RAS-PROTOCOL-TUNNEL.asn
--
-- $Id: RAS-PROTOCOL-TUNNEL.asn 23309 2007-10-29 19:25:37Z kukosa $
--

-- Module RAS-PROTOCOL-TUNNEL (H.323:06/2006)
RAS-PROTOCOL-TUNNEL DEFINITIONS AUTOMATIC TAGS ::=
BEGIN

IMPORTS TunnelledProtocol, NonStandardParameter
          FROM H323-MESSAGES;

RasTunnelledSignallingMessage ::= SEQUENCE {
  tunnelledProtocolID  TunnelledProtocol, -- tunnelled signalling protocol ID
  messageContent       SEQUENCE OF OCTET STRING, -- sequence of entire message(s)
  tunnellingRequired   NULL OPTIONAL,
  nonStandardData      NonStandardParameter OPTIONAL,
  ...
}

END

-- Generated by Asnp, the ASN.1 pretty-printer of France Telecom R&D
