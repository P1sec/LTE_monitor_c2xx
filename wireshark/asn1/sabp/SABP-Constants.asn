-- SABP-Constants.asn
--
-- Taken from 3GPP TS 25.419 V11.0.0 (2012-09)
-- http://www.3gpp.org/ftp/Specs/archive/25_series/25.419/25419-700.zip/25419-700.DOC
--
-- 9.3.6	Constant Definitions
--
-- $Id: SABP-Constants.asn 47192 2013-01-21 07:09:13Z etxrab $
--

-- **************************************************************
--
-- Constant definitions
--
-- **************************************************************

SABP-Constants {
itu-t (0) identified-organization (4) etsi (0) mobileDomain (0) 
umts-Access (20) modules (3) sabp (3) version1 (1) sabp-Constants (4) } 

DEFINITIONS AUTOMATIC TAGS ::= 

BEGIN

-- **************************************************************
--
-- Elementary Procedures
--
-- **************************************************************

id-Write-Replace 			INTEGER ::= 0
id-Kill 				INTEGER ::= 1
id-Load-Status-Enquiry 			INTEGER ::= 2
id-Message-Status-Query 		INTEGER ::= 3
id-Restart-Indication			INTEGER ::= 4
id-Reset 				INTEGER ::= 5
id-Failure-Indication			INTEGER ::= 6
id-Error-Indication			INTEGER ::= 7

-- **************************************************************
--
-- IEs
--
-- **************************************************************

id-Broadcast-Message-Content		INTEGER ::= 0
id-Category 				INTEGER ::= 1
id-Cause 				INTEGER ::= 2
id-Criticality-Diagnostics	INTEGER ::=3
id-Data-Coding-Scheme 			INTEGER ::= 4
id-Failure-List 			INTEGER ::= 5
id-Message-Identifier 			INTEGER ::= 6
id-New-Serial-Number			INTEGER ::= 7
id-Number-of-Broadcasts-Completed-List 	INTEGER ::= 8
id-Number-of-Broadcasts-Requested 		INTEGER ::= 9
id-Old-Serial-Number				INTEGER ::= 10
id-Radio-Resource-Loading-List 		INTEGER ::= 11
id-Recovery-Indication 			INTEGER ::= 12
id-Repetition-Period 			INTEGER ::= 13
id-Serial-Number 			INTEGER ::= 14
id-Service-Areas-List 			INTEGER ::= 15
id-MessageStructure				INTEGER ::= 16
id-TypeOfError					INTEGER ::= 17
id-Paging-ETWS-Indicator		INTEGER ::= 18
id-Warning-Type					INTEGER ::= 19
id-WarningSecurityInfo			INTEGER ::= 20 
id-Broadcast-Message-Content-Validity-Indicator 	INTEGER ::= 21

-- **************************************************************
--
-- Extension constants
--
-- **************************************************************

-- **************************************************************
--
-- Lists
--
-- **************************************************************

maxNrOfErrors				INTEGER ::= 256 
maxnoofSAI			INTEGER ::= 65535 

maxProtocolExtensions 			INTEGER ::= 65535
maxProtocolIEs				INTEGER ::= 65535
maxNrOfLevels						INTEGER ::= 256

END
