-- $Id: CAP-classes.asn 39386 2011-10-12 16:41:42Z etxrab $
-- 3GPP TS 29.078 11.0.0 (2011-09)
-- 5.5	Classes
CAP-classes {itu-t(0) identified-organization(4) etsi(0) mobileDomain(0) umts-network(1)
modules(3) cap-classes(54) version8(7)}

DEFINITIONS ::= BEGIN

IMPORTS

	ROS-OBJECT-CLASS,
	Code
FROM Remote-Operations-Information-Objects ros-InformationObjects

	id-rosObject-gprsSSF,
	id-rosObject-gsmSRF,
	id-rosObject-gsmSSF,
	id-rosObject-smsSSF-V3,
	id-rosObject-smsSSF-V4,
	ros-InformationObjects,
	gsmSSF-gsmSCF-Protocol,
	gsmSCF-gsmSRF-Protocol,
	smsSSF-gsmSCF-Protocol,
	gprsSSF-gsmSCF-Protocol
FROM CAP-object-identifiers {itu-t(0) identified-organization(4) etsi(0) mobileDomain(0)
umts-network(1) modules(3) cap-object-identifiers(100) version8(7)}

	capSsfToScfGeneric,
	capAssistHandoffssfToScf,
	capScfToSsfGeneric
FROM CAP-gsmSSF-gsmSCF-pkgs-contracts-acs gsmSSF-gsmSCF-Protocol

	gsmSRF-gsmSCF-contract
FROM CAP-gsmSCF-gsmSRF-pkgs-contracts-acs gsmSCF-gsmSRF-Protocol

	cap3SMS,
	cap4SMS
FROM CAP-smsSSF-gsmSCF-pkgs-contracts-acs smsSSF-gsmSCF-Protocol

	capGprsSsfToScf,
	capGsmScfToGprsSsf
FROM CAP-gprsSSF-gsmSCF-pkgs-contracts-acs gprsSSF-gsmSCF-Protocol

	CriticalityType
FROM CS2-datatypes {itu-t(0) identified-organization(4) etsi(0) inDomain(1) in-network(1) cs2(20)
modules(0) in-cs2-datatypes(0) version1(0)}

;

gsmSSF ROS-OBJECT-CLASS ::= {
	INITIATES	{capSsfToScfGeneric|
				capAssistHandoffssfToScf}
	RESPONDS	{capScfToSsfGeneric}
	ID			id-rosObject-gsmSSF}
-- The Rel-6 'gsmSSF' definition uses the Rel-6 capSsfToScfGeneric, capAssistHandoffssfToScf
-- and capScfToSsfGeneric CONTRACT definitions.

gsmSRF ROS-OBJECT-CLASS ::= {
	INITIATES	{gsmSRF-gsmSCF-contract}
	ID			id-rosObject-gsmSRF}
-- The Rel-6 'gsmSRF' definition uses the Rel-6 gsmSRF-gsmSCF-contract CONTRACT definition.

smsSSF-V3 ROS-OBJECT-CLASS ::= {
	INITIATES	{cap3SMS}
	ID			id-rosObject-smsSSF-V3}
-- The Rel-6 'smsSSF-V3' definition uses the Rel-6 cap3SMS CONTRACT definition. The smsSSF-V3
-- ROS-OBJECT-CLASS is used for MO SMS control.

smsSSF-V4 ROS-OBJECT-CLASS ::= {
	INITIATES	{cap4SMS}
	ID			id-rosObject-smsSSF-V4}
-- The Rel-6 'smsSSF-V4' definition uses the Rel-6 cap4SMS CONTRACT definition. The smsSSF-V4
-- ROS-OBJECT-CLASS is used for MT SMS control.

gprsSSF ROS-OBJECT-CLASS ::= {
	INITIATES	{capGprsSsfToScf}
	RESPONDS	{capGsmScfToGprsSsf}
	ID			id-rosObject-gprsSSF}
-- The Rel-6 'gprsSSF' definition uses the Rel-6 capGprsSsfTogsmScf and capGsmScfToGprsSsf
-- CONTRACT definitions.

EXTENSION ::= CLASS {
	&ExtensionType,
	&criticality		CriticalityType DEFAULT ignore,
	&id	Code}

WITH SYNTAX {
	EXTENSION-SYNTAX	&ExtensionType
	CRITICALITY			&criticality
	IDENTIFIED BY		&id
	}
-- Only value Global OBJECT IDENTIFIER is used for &id;
-- Only the value ignore (0) is used for &criticality.

-- Example of addition of an extension named 'Some Network Specific Indicator' of type
-- BOOLEAN, with criticality 'ignore' and identified by global Object Identifier.
--
-- Example of definition using the above information object class:
--
-- SomeNetworkSpecificIndicator EXTENSION ::= {
-- 	EXTENSION-SYNTAX	BOOLEAN
--	CRITICALITY			ignore
--	IDENTIFIED BY		global : {itu-t(0) identified-organization(4) organisation(0) gsm(1)
--								 capextension(2)}
--	}

-- Example of transfer syntax, using the ExtensionField datatype as specified in clause 5.
-- Assuming the value of the extension is set to TRUE, the extensions parameter becomes
-- a Sequence of type {itu-t(0) identified-organization(4) organisation(0) gsm(1)
-- capextension(2)}, criticality ENUMERATED ::= ignore(0) and value [1] EXPLICIT BOOLEAN
-- ::= TRUE.
--
-- Use of ITU-T Recommendation Q.1400 [52] defined Extension is for further study.
-- In addition the extension mechanism marker is used to identify the future minor additions
-- to CAP.

firstExtension EXTENSION ::= {
	EXTENSION-SYNTAX	NULL
	CRITICALITY			ignore
	IDENTIFIED BY		global : {itu-t(0) identified-organization(4) organisation(0) gsm(1)
						capextension(2)}
	}
-- firstExtension is just an example.

SupportedExtensions EXTENSION ::= {firstExtension, ...
-- full set of network operator extensions –-
}
-- SupportedExtension is the full set of the network operator extensions.

PARAMETERS-BOUND ::= CLASS {
	&minAccessPointNameLength					INTEGER,
	&maxAccessPointNameLength					INTEGER,
	&minAChBillingChargingLength				INTEGER,
	&maxAChBillingChargingLength				INTEGER,
	&minAttributesLength						INTEGER,
	&maxAttributesLength						INTEGER,
	&maxBearerCapabilityLength					INTEGER,
	&minCalledPartyBCDNumberLength				INTEGER,
	&maxCalledPartyBCDNumberLength				INTEGER,
	&minCalledPartyNumberLength					INTEGER,
	&maxCalledPartyNumberLength					INTEGER,
	&minCallingPartyNumberLength				INTEGER,
	&maxCallingPartyNumberLength				INTEGER,
	&minCallResultLength						INTEGER,
	&maxCallResultLength						INTEGER,
	&minCarrierLength							INTEGER,
	&maxCarrierLength							INTEGER,
	&minCauseLength								INTEGER,
	&maxCauseLength								INTEGER,
	&minDigitsLength							INTEGER,
	&maxDigitsLength							INTEGER,
	&minFCIBillingChargingDataLength			INTEGER,
	&maxFCIBillingChargingDataLength			INTEGER,
	&minFCIBillingChargingLength				INTEGER,
	&maxFCIBillingChargingLength				INTEGER,
	&minGenericNumberLength						INTEGER,
	&maxGenericNumberLength						INTEGER,
	&minGPRSCauseLength							INTEGER,
	&maxGPRSCauseLength							INTEGER,
	&minIPSSPCapabilitiesLength					INTEGER,
	&maxIPSSPCapabilitiesLength					INTEGER,
	&minLocationNumberLength					INTEGER,
	&maxLocationNumberLength					INTEGER,
	&minLowLayerCompatibilityLength             INTEGER,
	&maxLowLayerCompatibilityLength             INTEGER,
	&minMessageContentLength					INTEGER,
	&maxMessageContentLength					INTEGER,
	&minOriginalCalledPartyIDLength				INTEGER,
	&maxOriginalCalledPartyIDLength				INTEGER,
	&minPDPAddressLength						INTEGER,
	&maxPDPAddressLength						INTEGER,
	&minRedirectingPartyIDLength				INTEGER,
	&maxRedirectingPartyIDLength				INTEGER,
	&minScfIDLength								INTEGER,
	&maxScfIDLength								INTEGER,
	&minSCIBillingChargingLength				INTEGER,
	&maxSCIBillingChargingLength				INTEGER,
	&minTimeAndTimezoneLength					INTEGER,
	&maxTimeAndTimezoneLength					INTEGER,
	&numOfBCSMEvents							INTEGER,
	&numOfChangeOfPositionControlInfo			INTEGER,
	&numOfCSs									INTEGER,
	&numOfSMSEvents								INTEGER,
	&numOfGPRSEvents							INTEGER,
	&numOfExtensions							INTEGER,
	&numOfGenericNumbers						INTEGER,
	&numOfMessageIDs							INTEGER}

WITH SYNTAX {
	MINIMUM-FOR-ACCESS-POINT-NAME				&minAccessPointNameLength
	MAXIMUM-FOR-ACCESS-POINT-NAME				&maxAccessPointNameLength
	MINIMUM-FOR-ACH-BILLING-CHARGING			&minAChBillingChargingLength
	MAXIMUM-FOR-ACH-BILLING-CHARGING			&maxAChBillingChargingLength
	MINIMUM-FOR-ATTRIBUTES						&minAttributesLength
	MAXIMUM-FOR-ATTRIBUTES						&maxAttributesLength
	MAXIMUM-FOR-BEARER-CAPABILITY				&maxBearerCapabilityLength
	MINIMUM-FOR-CALLED-PARTY-BCD-NUMBER			&minCalledPartyBCDNumberLength
	MAXIMUM-FOR-CALLED-PARTY-BCD-NUMBER			&maxCalledPartyBCDNumberLength
	MINIMUM-FOR-CALLED-PARTY-NUMBER				&minCalledPartyNumberLength
	MAXIMUM-FOR-CALLED-PARTY-NUMBER				&maxCalledPartyNumberLength
	MINIMUM-FOR-CALLING-PARTY-NUMBER			&minCallingPartyNumberLength
	MAXIMUM-FOR-CALLING-PARTY-NUMBER			&maxCallingPartyNumberLength
	MINIMUM-FOR-CALL-RESULT						&minCallResultLength
	MAXIMUM-FOR-CALL-RESULT						&maxCallResultLength
	MINIMUM-FOR-CARRIER							&minCarrierLength
	MAXIMUM-FOR-CARRIER							&maxCarrierLength
	MINIMUM-FOR-CAUSE							&minCauseLength
	MAXIMUM-FOR-CAUSE							&maxCauseLength
	MINIMUM-FOR-DIGITS							&minDigitsLength
	MAXIMUM-FOR-DIGITS							&maxDigitsLength
	MINIMUM-FOR-FCI-BILLING-CHARGING-DATA		&minFCIBillingChargingDataLength
	MAXIMUM-FOR-FCI-BILLING-CHARGING-DATA		&maxFCIBillingChargingDataLength
	MINIMUM-FOR-FCI-BILLING-CHARGING			&minFCIBillingChargingLength
	MAXIMUM-FOR-FCI-BILLING-CHARGING			&maxFCIBillingChargingLength
	MINIMUM-FOR-GENERIC-NUMBER					&minGenericNumberLength
	MAXIMUM-FOR-GENERIC-NUMBER					&maxGenericNumberLength
	MINIMUM-FOR-GPRS-CAUSE-LENGTH				&minGPRSCauseLength
	MAXIMUM-FOR-GPRS-CAUSE-LENGTH				&maxGPRSCauseLength
	MINIMUM-FOR-IP-SSP-CAPABILITIES				&minIPSSPCapabilitiesLength
	MAXIMUM-FOR-IP-SSP-CAPABILITIES				&maxIPSSPCapabilitiesLength
	MINIMUM-FOR-LOCATION-NUMBER					&minLocationNumberLength
	MAXIMUM-FOR-LOCATION-NUMBER					&maxLocationNumberLength
    MINIMUM-FOR-LOW-LAYER-COMPATIBILITY			&minLowLayerCompatibilityLength
	MAXIMUM-FOR-LOW-LAYER-COMPATIBILITY 		&maxLowLayerCompatibilityLength
	MINIMUM-FOR-MESSAGE-CONTENT					&minMessageContentLength
	MAXIMUM-FOR-MESSAGE-CONTENT					&maxMessageContentLength
	MINIMUM-FOR-ORIGINAL-CALLED-PARTY-ID		&minOriginalCalledPartyIDLength
	MAXIMUM-FOR-ORIGINAL-CALLED-PARTY-ID		&maxOriginalCalledPartyIDLength
	MINIMUM-FOR-PDP-ADDRESS-LENGTH				&minPDPAddressLength
	MAXIMUM-FOR-PDP-ADDRESS-LENGTH				&maxPDPAddressLength
	MINIMUM-FOR-REDIRECTING-ID					&minRedirectingPartyIDLength
	MAXIMUM-FOR-REDIRECTING-ID					&maxRedirectingPartyIDLength
	MINIMUM-FOR-GSMSCF-ID						&minScfIDLength
	MAXIMUM-FOR-GSMSCF-ID						&maxScfIDLength
	MINIMUM-FOR-SCI-BILLING-CHARGING			&minSCIBillingChargingLength
	MAXIMUM-FOR-SCI-BILLING-CHARGING			&maxSCIBillingChargingLength
	MINIMUM-FOR-TIME-AND-TIMEZONE				&minTimeAndTimezoneLength
	MAXIMUM-FOR-TIME-AND-TIMEZONE				&maxTimeAndTimezoneLength
	NUM-OF-BCSM-EVENT							&numOfBCSMEvents
	NUM-OF-CHANGE-OF-POSITION-CONTROL-INFO		&numOfChangeOfPositionControlInfo
	NUM-OF-CSS									&numOfCSs
	NUM-OF-SMS-EVENTS							&numOfSMSEvents
	NUM-OF-GPRS-EVENTS							&numOfGPRSEvents
	NUM-OF-EXTENSIONS							&numOfExtensions
	NUM-OF-GENERIC-NUMBERS						&numOfGenericNumbers
	NUM-OF-MESSAGE-IDS							&numOfMessageIDs}

cAPSpecificBoundSet PARAMETERS-BOUND ::= {
	MINIMUM-FOR-ACCESS-POINT-NAME				1
	MAXIMUM-FOR-ACCESS-POINT-NAME				100
	MINIMUM-FOR-ACH-BILLING-CHARGING			5
	MAXIMUM-FOR-ACH-BILLING-CHARGING			177
	MINIMUM-FOR-ATTRIBUTES						2
	MAXIMUM-FOR-ATTRIBUTES						10
	MAXIMUM-FOR-BEARER-CAPABILITY				11
	MINIMUM-FOR-CALLED-PARTY-BCD-NUMBER			1
	MAXIMUM-FOR-CALLED-PARTY-BCD-NUMBER			41
	MINIMUM-FOR-CALLED-PARTY-NUMBER				2
	MAXIMUM-FOR-CALLED-PARTY-NUMBER				18
	MINIMUM-FOR-CALLING-PARTY-NUMBER			2
	MAXIMUM-FOR-CALLING-PARTY-NUMBER			10
	MINIMUM-FOR-CALL-RESULT						12
	MAXIMUM-FOR-CALL-RESULT						193
	MINIMUM-FOR-CARRIER							4
	MAXIMUM-FOR-CARRIER							4
	MINIMUM-FOR-CAUSE							2
	MAXIMUM-FOR-CAUSE							32
	MINIMUM-FOR-DIGITS							2
	MAXIMUM-FOR-DIGITS							16
	MINIMUM-FOR-FCI-BILLING-CHARGING-DATA		1
	MAXIMUM-FOR-FCI-BILLING-CHARGING-DATA		160
	MINIMUM-FOR-FCI-BILLING-CHARGING			5
	MAXIMUM-FOR-FCI-BILLING-CHARGING			225
	MINIMUM-FOR-GENERIC-NUMBER					3
	MAXIMUM-FOR-GENERIC-NUMBER					11
	MINIMUM-FOR-GPRS-CAUSE-LENGTH				1
	MAXIMUM-FOR-GPRS-CAUSE-LENGTH				1
	MINIMUM-FOR-IP-SSP-CAPABILITIES				1
	MAXIMUM-FOR-IP-SSP-CAPABILITIES				4
	MINIMUM-FOR-LOCATION-NUMBER					2
	MAXIMUM-FOR-LOCATION-NUMBER					10
	MINIMUM-FOR-LOW-LAYER-COMPATIBILITY		    1
	MAXIMUM-FOR-LOW-LAYER-COMPATIBILITY		    16
	MINIMUM-FOR-MESSAGE-CONTENT					1
	MAXIMUM-FOR-MESSAGE-CONTENT					127
	MINIMUM-FOR-ORIGINAL-CALLED-PARTY-ID		2
	MAXIMUM-FOR-ORIGINAL-CALLED-PARTY-ID		10
	MINIMUM-FOR-PDP-ADDRESS-LENGTH				1
	MAXIMUM-FOR-PDP-ADDRESS-LENGTH				63
	MINIMUM-FOR-REDIRECTING-ID					2
	MAXIMUM-FOR-REDIRECTING-ID					10
	MINIMUM-FOR-GSMSCF-ID						2
	MAXIMUM-FOR-GSMSCF-ID						10
	MINIMUM-FOR-SCI-BILLING-CHARGING			4
	MAXIMUM-FOR-SCI-BILLING-CHARGING			225
	MINIMUM-FOR-TIME-AND-TIMEZONE				8
	MAXIMUM-FOR-TIME-AND-TIMEZONE				8
	NUM-OF-BCSM-EVENT							30
	NUM-OF-CHANGE-OF-POSITION-CONTROL-INFO		10
	NUM-OF-CSS									127
	NUM-OF-SMS-EVENTS							10
	NUM-OF-GPRS-EVENTS							10
	NUM-OF-EXTENSIONS							10
	NUM-OF-GENERIC-NUMBERS						5
	NUM-OF-MESSAGE-IDS							16}

END
