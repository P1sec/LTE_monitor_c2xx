-- RRLP-Messages.asn
-- $Id: RRLP-Messages.asn 42351 2012-04-30 16:45:03Z pascal $
-- Taken from 3GPP TS 44.031 V9.2.0 (2010-03)
-- http://www.3gpp.org/ftp/Specs/archive/44_series/44.031/44031-920.zip/44031-920.doc
--
-- 3.1 General Format of RRLP Message
--

RRLP-Messages
-- { RRLP-messages }

DEFINITIONS AUTOMATIC TAGS ::=

BEGIN

IMPORTS
	MsrPosition-Req, MsrPosition-Rsp, AssistanceData,
	ProtocolError, PosCapability-Req, PosCapability-Rsp
FROM
	RRLP-Components 	-- { RRLP-Components }
;

PDU ::= SEQUENCE {
	referenceNumber			INTEGER (0..7),
	component				RRLP-Component
}

RRLP-Component ::= CHOICE {
	msrPositionReq			MsrPosition-Req,
	msrPositionRsp			MsrPosition-Rsp,
	assistanceData			AssistanceData,
	assistanceDataAck		NULL,
	protocolError			ProtocolError,
	...,
	posCapabilityReq		PosCapability-Req,
	posCapabilityRsp		PosCapability-Rsp
}

END
