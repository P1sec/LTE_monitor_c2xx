-- QSIG-WTMCH.asn
--
-- Taken from Ecma International
-- Standard ECMA-304, 2nd edition (December 2001)
-- http://www.ecma-international.org/publications/standards/Ecma-304.htm
--
-- $Id: QSIG-WTMCH.asn 22361 2007-07-20 09:54:47Z kukosa $
--

Wireless-Terminal-Call-Handling-Operations-asn1-97  
   { iso (1)  standard (0)  pss1-wtm-call-handling (15431)  operations-asn1-97 (1)} 
 
DEFINITIONS EXPLICIT TAGS ::= 
 
BEGIN 
IMPORTS  OPERATION, ERROR FROM Remote-Operations-Information-Objects 
    { joint-iso-itu-t remote-operations (4) informationObjects(5) version1(0)} 
  EXTENSION, Extension{} FROM Manufacturer-specific-service-extension-class-asn1-97 
    { iso (1) standard (0) 
    pss1-generic-procedures (11582) msi-class-asn1-97 (11) } 
  PSS1InformationElement FROM PSS1-generic-parameters-definition-asn1-97 
    { iso (1) standard (0) 
    pss1-generic-procedures (11582) pss1-generic-parameters-asn1-97 (17) } 
  Name FROM Name-Operations-asn1-97 
    { iso (1) standard (0) 
    pss1-name (13868) name-operations-asn1-97 (1) } 
 basicServiceNotProvided, invalidServedUserNr, notAvailable FROM  
   General-Error-List 
    { ccitt (0) recommendation (0) q 950 general-error-list (1) } 
  Address, PartyNumber, PartySubaddress, PresentedNumberScreened FROM  
   Addressing-Data-Elements-asn1-97 
    { iso (1) standard (0) pss1-generic-procedures (11582)  
    addressing-data-elements-asn1-97 (20) }; 
 
-- Operations for ANF-WTMI: -- 
 
WTMCH-Operations OPERATION ::= {wtmiEnquiry | wtmiDivert | wtmiInform| wtmoCall} 
 
wtmiEnquiry   OPERATION ::= { 
  -- Sent from the WTMI-detect PINX to the Home PINX. 
   ARGUMENT  EnquiryArg 
   RESULT  EnquiryRes 
    ERRORS  { invalidServedUserNr | locationNotKnown |  
      notAvailable | basicServiceNotProvided | unspecified } 
   CODE  local: 54} 

wtmiDivert   OPERATION ::= { 
  -- Sent from the WTMI-detect PINX to the Rerouteing PINX. 
   ARGUMENT  DivertArg 
   RESULT  DummyRes 
    ERRORS  { notAvailable | unspecified } 
   CODE  local: 55} 
wtmiInform   OPERATION ::= { 
  -- Sent from the Rerouteing PINX to the Visitor PINX. 
   ARGUMENT      InformArg 
   RETURN RESULT    FALSE 
    ALWAYS RESPONDS   FALSE 
   CODE      local: 56} 
 
EnquiryArg ::=  SEQUENCE   { pisnNumber    PartyNumber, 
     -- The PISN number of the WTMI user 
     qSIGInfoElement  PSS1InformationElement, 
  -- The basic call information elements Bearer capability, High layer compatibility, 
  -- Low layer compatibility can be embedded in the qSIGInfoElement 
  -- in accordance with clause 6.5.2.1. 
      argExtension    WtmiExtension OPTIONAL } 
DivertArg ::=  SEQUENCE   { visitPINX    PartyNumber, 
     -- The PISN number of the Visitor PINX, 
      -- always a Complete Number.  
     callingNumber    PresentedNumberScreened, 
     wtmIdentity    WtmIdentity, 
     -- The PISN number (always a Complete Number) 
      -- and/or an alternative identifier of the WTMI user. 
     qSIGInfoElement  PSS1InformationElement, 
  -- The basic call information elements Bearer capability, High layer compatibility, 
  -- Low layer compatibility, and Progress indicator  
  -- can be embedded in the qSIGInfoElement in accordance with clause 6.5.2.1. 
      callingUserSub   [ 1 ] PartySubaddress OPTIONAL, 
      callingName    [ 2 ] Name OPTIONAL, 
      wtmUserSub    [ 3 ] PartySubaddress OPTIONAL, 
      argExtension    WtmiExtension OPTIONAL } 
InformArg ::=  SEQUENCE  { wtmIdentity   WtmIdentity, 
     -- The PISN number (always a Complete Number) 
      -- and/or an alternative identifier of the WTMI user. 
      argExtension    WtmiExtension OPTIONAL } 
EnquiryRes ::=  CHOICE  { currLocation    [ 1 ] IMPLICIT CurrLocation, 
      cfuActivated    [ 2 ] IMPLICIT CfuActivated } 
CurrLocation  ::=  SEQUENCE  { visitPINX    PartyNumber, 
     -- The PISN number of the Visitor PINX, 
      -- always a Complete Number.  
     wtmIdentity    WtmIdentity, 
     -- The PISN number (always a Complete Number) 
      -- and/or an alternative identifier of the WTMI user  
      argExtension    WtmiExtension OPTIONAL } 

CfuActivated  ::=  SEQUENCE  { divToAddress   Address, 
     divOptions    SubscriptionOption, 
      wtmName    [ 1 ] Name OPTIONAL,  
      argExtension     WtmiExtension OPTIONAL } 
SubscriptionOption ::=  ENUMERATED    { noNotification (0), 
     notificationWithoutDivertedToNr (1), 
      notificationWithDivertedToNr (2) } 
DummyRes ::=  CHOICE  { null    NULL, 
      extension  [ 1 ] IMPLICIT Extension{{WTMCHExtSet}}, 
      sequOfExtn  [ 2 ] IMPLICIT SEQUENCE OF  
           Extension{{WTMCHExtSet}} } 
WtmiExtension ::=  CHOICE  { extension  [ 4 ] IMPLICIT Extension{{WTMCHExtSet}}, 
      sequOfExtn  [ 5 ] IMPLICIT SEQUENCE OF  
           Extension{{WTMCHExtSet}} } 
WtmIdentity  ::=  CHOICE  { pisnNumber  PartyNumber, 
      alternativeId  [ 10 ] IMPLICIT AlternativeId, 
      both    [ 11 ] IMPLICIT SEQUENCE 
         { pisnNumber  PartyNumber, 
            alternativeId  AlternativeId } } 
AlternativeId ::=  OCTET STRING(SIZE(1..20)) 
 
-- Operation for ANF-WTMO -- 
wtmoCall   OPERATION ::= { 
 ARGUMENT  WtmoArg 
 RETURN RESULT  FALSE 
 ALWAYS RESPONDS  FALSE 
 CODE   local: 71} 
WtmoArg ::= SEQUENCE {  
  destinationNumber  [0]  PartyNumber  OPTIONAL, 
  sendingComplete  [1]  IMPLICIT NULL  OPTIONAL, 
  extension  CHOICE     
      {single  [2] IMPLICIT Extension{{WTMCHExtSet}}, 
      multiple  [3] IMPLICIT SEQUENCE OF  
           Extension{{WTMCHExtSet}}  
      } OPTIONAL     
 } 
 
WTMCHExtSet EXTENSION ::= {...} 
 
unspecified  ERROR ::= {   
   PARAMETER   Extension{{WTMCHExtSet}} 
   CODE  local: 1008} 
locationNotKnown  ERROR ::= { CODE  local: 1015} 
 
END  -- of Wireless-Terminal-Call-Handling-Operations-asn1-97
