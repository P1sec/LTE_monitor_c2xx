-- SIGNALLING-TRAVERSAL.asn
--
-- Taken from ITU ASN.1 database
-- http://www.itu.int/ITU-T/asn1/database/itu-t/h/h460.18/2005/SIGNALLING-TRAVERSAL.asn
--
-- $Id: SIGNALLING-TRAVERSAL.asn 23260 2007-10-24 06:56:07Z guy $
--

-- Module SIGNALLING-TRAVERSAL (H.460.18:09/2005)
SIGNALLING-TRAVERSAL {itu-t(0) recommendation(0) h(8) 460 18 version(0) 1}
DEFINITIONS AUTOMATIC TAGS ::=
BEGIN

IMPORTS CallIdentifier, TimeToLive, TransportAddress
          FROM H323-MESSAGES;

IncomingCallIndication ::= SEQUENCE {
  callSignallingAddress  TransportAddress,
  callID                 CallIdentifier,
  ...
}

LRQKeepAliveData ::= SEQUENCE {
  lrqKeepAliveInterval  TimeToLive, -- keep-alive interval (seconds)
  ...
}

END

-- Generated by Asnp, the ASN.1 pretty-printer of France Telecom R&D
