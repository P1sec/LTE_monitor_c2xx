-- NUMBER-PORTABILITY.asn
--
-- Taken from ITU ASN.1 database
-- http://www.itu.int/ITU-T/asn1/database/itu-t/h/h460.2/2001/NUMBER-PORTABILITY.asn
--
-- $Id: NUMBER-PORTABILITY.asn 23274 2007-10-26 07:18:44Z kukosa $
--

-- Module NUMBER-PORTABILITY (H.460.2:07/2001)
NUMBER-PORTABILITY DEFINITIONS AUTOMATIC TAGS ::=
BEGIN

IMPORTS
  PublicTypeOfNumber, PrivateTypeOfNumber, AliasAddress
    FROM H323-MESSAGES;

NumberPortabilityInfo ::= CHOICE {
  numberPortabilityRejectReason  NumberPortabilityRejectReason,
  nUMBERPORTABILITYDATA
    SEQUENCE {addressTranslated  NULL OPTIONAL,
              portedAddress      PortabilityAddress OPTIONAL,
              routingAddress     PortabilityAddress OPTIONAL,
              regionalParams     RegionalParameters OPTIONAL,
              ...},
  ...
}

NumberPortabilityRejectReason ::= CHOICE {
  unspecified      NULL,
  qorPortedNumber  NULL,
  ...
}

PortabilityAddress ::= SEQUENCE {
  aliasAddress   AliasAddress,
  typeOfAddress  NumberPortabilityTypeOfNumber OPTIONAL,
  ...
}

NumberPortabilityTypeOfNumber ::= CHOICE {
  publicTypeOfNumber       PublicTypeOfNumber,
  privateTypeOfNumber      PrivateTypeOfNumber,
  portabilityTypeOfNumber  PortabilityTypeOfNumber,
  ...
}

PortabilityTypeOfNumber ::= CHOICE {
  portedNumber        NULL,
  routingNumber       NULL,
  concatenatedNumber  NULL,
  ...
}

RegionalParameters ::= SEQUENCE {
  t35CountryCode     INTEGER(0..255),
  t35Extension       INTEGER(0..255),
  variantIdentifier  INTEGER(1..255) OPTIONAL,
  regionalData       OCTET STRING,
  ...
}

END

-- Generated by Asnp, the ASN.1 pretty-printer of France Telecom R&D
