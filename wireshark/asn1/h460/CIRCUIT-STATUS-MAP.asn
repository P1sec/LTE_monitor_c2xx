-- CIRCUIT-STATUS-MAP.asn
--
-- Taken from ITU ASN.1 database
-- http://www.itu.int/ITU-T/asn1/database/itu-t/h/h460.3/2002/CIRCUIT-STATUS-MAP.asn
--
-- $Id: CIRCUIT-STATUS-MAP.asn 23274 2007-10-26 07:18:44Z kukosa $
--

-- Module CIRCUIT-STATUS-MAP (H.460.3:11/2002)
CIRCUIT-STATUS-MAP DEFINITIONS AUTOMATIC TAGS ::=
BEGIN

IMPORTS CircuitIdentifier
          FROM H323-MESSAGES;

CircuitStatus ::= SEQUENCE -- root for Circuit Status Map ASN.1
                   {
  circuitStatusMap  SEQUENCE OF CircuitStatusMap OPTIONAL,
  ...
}

CircuitStatusMap ::= SEQUENCE {
  statusType     CircuitStatusType,
  baseCircuitID  CircuitIdentifier,
  range          INTEGER(0..4095),
  status         OCTET STRING,
  ...
}

CircuitStatusType ::= CHOICE {
  serviceStatus  NULL, -- status: 0 = out-of-service, 1 = in-service
  busyStatus     NULL, -- status: 0 = free, 1 = in-use
  ...
}

END

-- Generated by Asnp, the ASN.1 pretty-printer of France Telecom R&D
