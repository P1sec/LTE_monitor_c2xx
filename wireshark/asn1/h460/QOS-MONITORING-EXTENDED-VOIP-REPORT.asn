-- QOS-MONITORING-EXTENDED-VOIP-REPORT.asn
--
-- Taken from ITU ASN.1 database
-- http://www.itu.int/ITU-T/asn1/database/itu-t/h/h460.9/2002/QOS-MONITORING-EXTENDED-VOIP-REPORT.asn
--
-- $Id: QOS-MONITORING-EXTENDED-VOIP-REPORT.asn 23274 2007-10-26 07:18:44Z kukosa $
--

-- Module QOS-MONITORING-EXTENDED-VOIP-REPORT (H.460.9:11/2002)
QOS-MONITORING-EXTENDED-VOIP-REPORT DEFINITIONS AUTOMATIC TAGS ::=
BEGIN

IMPORTS GenericIdentifier
          FROM H323-MESSAGES;

ExtendedRTPMetrics ::= SEQUENCE {
  networkPacketLossRate    INTEGER(0..255) OPTIONAL,
  jitterBufferDiscardRate  INTEGER(0..255) OPTIONAL,
  burstMetrics             BurstMetrics OPTIONAL,
  rtcpRoundTripDelay       INTEGER(0..65535) OPTIONAL,
  endSystemDelay           INTEGER(0..65535) OPTIONAL,
  signalLevel              INTEGER(-127..10) OPTIONAL,
  noiseLevel               INTEGER(-127..0) OPTIONAL,
  residualEchoReturnLoss   INTEGER(0..127) OPTIONAL,
  rFactor                  INTEGER(0..100) OPTIONAL,
  extRFactor               INTEGER(0..100) OPTIONAL,
  estimatedMOSLQ           INTEGER(10..50) OPTIONAL,
  estimatedMOSCQ           INTEGER(10..50) OPTIONAL,
  plcType                  PLCtypes OPTIONAL,
  jitterBufferParms        JitterBufferParms OPTIONAL,
  ...
}

BurstMetrics ::= SEQUENCE {
  gmin              INTEGER(0..255) OPTIONAL,
  burstLossDensity  INTEGER(0..255) OPTIONAL,
  gapLossDensity    INTEGER(0..255) OPTIONAL,
  burstDuration     INTEGER(0..65535) OPTIONAL,
  gapDuration       INTEGER(0..65535) OPTIONAL,
  ...
}

PLCtypes ::= CHOICE {
  unspecified  NULL,
  disabled     NULL,
  enhanced     NULL,
  standard     NULL,
  ...
}

JitterBufferParms ::= SEQUENCE {
  jitterBufferType         JitterBufferTypes OPTIONAL,
  jitterBufferAdaptRate    INTEGER(0..15) OPTIONAL,
  jitterBufferNominalSize  INTEGER(0..65535) OPTIONAL,
  jitterBufferMaxSize      INTEGER(0..65535) OPTIONAL,
  jitterBufferAbsoluteMax  INTEGER(0..65535) OPTIONAL,
  ...
}

JitterBufferTypes ::= CHOICE {
  unknown      NULL,
  reserved     NULL,
  nonadaptive  NULL,
  adaptive     NULL,
  ...
}

qosMonitoringExtendedRTPMetrics GenericIdentifier ::= standard:2

END -- of QOS-MONITORING-EXTENDED-VOIP-REPORT

-- Generated by Asnp, the ASN.1 pretty-printer of France Telecom R&D
