-- MESSAGE-BROADCAST.asn
--
-- Taken from ITU ASN.1 database
-- http://www.itu.int/ITU-T/asn1/database/itu-t/h/h460.21/2006/MESSAGE-BROADCAST.asn
--
-- $Id: MESSAGE-BROADCAST.asn 23274 2007-10-26 07:18:44Z kukosa $
--

-- Module MESSAGE-BROADCAST (H.460.21:05/2006)
MESSAGE-BROADCAST DEFINITIONS AUTOMATIC TAGS ::=
BEGIN

IMPORTS
  MulticastAddress, UnicastAddress, Capability
    FROM MULTIMEDIA-SYSTEM-CONTROL;

CapabilityAdvertisement ::= SEQUENCE {
  receiveCapabilities   ReceiveCapabilities OPTIONAL,
  transmitCapabilities  SEQUENCE SIZE (1..256) OF TransmitCapabilities OPTIONAL,
  ...
}

ReceiveCapabilities ::= SEQUENCE {
  capabilities  SEQUENCE SIZE (1..256) OF Capability,
  maxGroups     INTEGER(1..65535),
  ...
}

GloballyUniqueID ::= OCTET STRING(SIZE (16))

TransmitCapabilities ::= SEQUENCE {
  groupIdentifer  GloballyUniqueID,
  capability      Capability,
  sourceAddress   UnicastAddress,
  ...
}

MessageBroadcastGroups ::= SEQUENCE SIZE (1..256) OF GroupAttributes

GroupAttributes ::= SEQUENCE {
  priority        INTEGER(0..255), -- 0 = high, 255 = low
  groupIdentifer  GloballyUniqueID OPTIONAL,
  capability      Capability,
  groupAddress    MulticastAddress,
  sourceAddress   UnicastAddress OPTIONAL,
  alertUser       BOOLEAN,
  ...
}

END

-- Generated by Asnp, the ASN.1 pretty-printer of France Telecom R&D
