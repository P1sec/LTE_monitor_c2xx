-- $Id: MAP-OperationAndMaintenanceOperations.asn 48195 2013-03-08 17:55:53Z etxrab $
-- 3GPP TS 29.002 V11.5.0 (2012-12) 
--17.6.2	Operation and Maintenance Operations
MAP-OperationAndMaintenanceOperations {
   itu-t identified-organization (4) etsi (0) mobileDomain (0)
   gsm-Network (1) modules (3) map-OperationAndMaintenanceOperations (6)
   version13 (13)}

DEFINITIONS

::=

BEGIN

EXPORTS
	activateTraceMode,
	deactivateTraceMode,
	sendIMSI
;

IMPORTS
	OPERATION
FROM Remote-Operations-Information-Objects {
joint-iso-itu-t remote-operations(4)
  informationObjects(5) version1(0)}

	systemFailure,
	dataMissing,
	unexpectedDataValue,
	facilityNotSupported,
	unknownSubscriber,
	unidentifiedSubscriber,
	tracingBufferFull
FROM MAP-Errors {
   itu-t identified-organization (4) etsi (0) mobileDomain (0)
   gsm-Network (1) modules (3) map-Errors (10) version13 (13)}

	ActivateTraceModeArg,
	ActivateTraceModeRes,
	DeactivateTraceModeArg,
	DeactivateTraceModeRes
FROM MAP-OM-DataTypes {
   itu-t identified-organization (4) etsi (0) mobileDomain (0)
   gsm-Network (1) modules (3) map-OM-DataTypes (12) version13 (13)}

	ISDN-AddressString,
	IMSI
FROM MAP-CommonDataTypes {
   itu-t identified-organization (4) etsi (0) mobileDomain (0)
   gsm-Network (1) modules (3) map-CommonDataTypes (18) version13 (13)}
;


activateTraceMode  OPERATION ::= {				--Timer m
	ARGUMENT
		ActivateTraceModeArg
	RESULT
		ActivateTraceModeRes
		-- optional
	ERRORS {
		systemFailure |
		dataMissing |
		unexpectedDataValue |
		facilityNotSupported |
		unidentifiedSubscriber |
		tracingBufferFull}
	CODE	local:50 }

deactivateTraceMode  OPERATION ::= {				--Timer m
	ARGUMENT
		DeactivateTraceModeArg
	RESULT
		DeactivateTraceModeRes
		-- optional
	ERRORS {
		systemFailure |
		dataMissing |
		unexpectedDataValue |
		facilityNotSupported |
		unidentifiedSubscriber}
	CODE	local:51 }

sendIMSI  OPERATION ::= {				--Timer m
	ARGUMENT
		ISDN-AddressString
	RESULT
		IMSI
	ERRORS {
		dataMissing |
		unexpectedDataValue |
		unknownSubscriber}
	CODE	local:58 }

END
