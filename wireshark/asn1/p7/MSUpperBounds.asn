-- $Id: MSUpperBounds.asn 31321 2009-12-19 14:26:26Z stig $
-- Module MSUpperBounds (X.413:06/1999)
-- See also ITU-T X.413 (06/1999)
-- See also the index of all ASN.1 assignments needed in this document

MSUpperBounds {joint-iso-itu-t mhs(6) ms(4) modules(0) upper-bounds(4)
  version-1994(0)} DEFINITIONS ::=
BEGIN

-- Exports everything
IMPORTS -- nothing -- ;

-- 	Upper Bounds
ub-alert-addresses INTEGER ::= 16

ub-attribute-values INTEGER ::= 32767 -- (215 - 1) the largest integer 

-- representable in 16 bits 
ub-attributes-supported INTEGER ::= 1024

ub-auto-action-errors INTEGER ::= 32767 -- (215 - 1) the largest integer 

-- representable in 16 bits 
ub-auto-actions INTEGER ::= 128

ub-auto-registrations INTEGER ::= 1024

ub-default-registrations INTEGER ::= 1024

ub-entry-classes INTEGER ::= 128

ub-entry-types INTEGER ::= 16

ub-error-reasons INTEGER ::= 16

ub-extensions INTEGER ::= 32

ub-group-depth INTEGER ::= 64

ub-group-descriptor-length INTEGER ::= 256

ub-group-part-length INTEGER ::= 128

ub-information-bases INTEGER ::= 16

ub-matching-rules INTEGER ::= 1024

ub-message-groups INTEGER ::= 8192

ub-message-notes-length INTEGER ::= 1024

ub-messages INTEGER ::= 2147483647 -- (231 - 1) the largest integer 

-- representable in 32 bits 
ub-modifications INTEGER ::=
  32767 -- (215 - 1) the largest integer 

-- representable in 16 bits 
ub-msstring-match INTEGER ::= 512

ub-per-auto-action INTEGER ::= 32767 -- (215 - 1) the largest integer 

-- representable in 16 bits 
ub-per-entry INTEGER ::= 1024

ub-service-information-length INTEGER ::= 2048

ub-summaries INTEGER ::= 16

ub-supplementary-info-length INTEGER ::= 256

ub-ua-registration-identifier-length INTEGER ::= 32

ub-ua-registrations INTEGER ::= 128

ub-ua-restrictions INTEGER ::= 16  -- renamed to avoid duplicate in MTSUpperBounds

END -- of MSUpperBounds

-- Generated by Asnp, the ASN.1 pretty-printer of France Telecom R&D
