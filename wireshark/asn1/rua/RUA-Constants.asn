-- RUA-Constants.asn
--
-- 3GPP TS 25.468 V9.1.0 (2010-03)
-- http://www.3gpp.org/ftp/Specs/html-info/25468.htm
--
-- 9.3.6	Constant definitions
--
-- $Id: RUA-Constants.asn 32779 2010-05-13 07:41:35Z etxrab $
--

-- **************************************************************
--
-- Constant definitions
--
-- **************************************************************

RUA-Constants { 
itu-t (0) identified-organization (4) etsi (0) mobileDomain (0) 
umts-Access (20) modules (3) rua(5) version1 (1) rUA-Constants (4) } 

DEFINITIONS AUTOMATIC TAGS ::= 

BEGIN

IMPORTS
	ProcedureCode,
	ProtocolIE-ID
FROM RUA-CommonDataTypes;


-- **************************************************************
--
-- Elementary Procedures
--
id-Connect							ProcedureCode ::= 1
id-DirectTransfer					ProcedureCode ::= 2
id-Disconnect						ProcedureCode ::= 3
id-ConnectionlessTransfer			ProcedureCode ::= 4
id-ErrorIndication					ProcedureCode ::= 5
id-privateMessage					ProcedureCode ::= 6

-- **************************************************************
--
-- Lists
--
-- **************************************************************
maxNrOfErrors						INTEGER ::= 256

-- **************************************************************
--
-- IEs
--
-- **************************************************************

id-Cause										ProtocolIE-ID ::= 1
id-CriticalityDiagnostics						ProtocolIE-ID ::= 2
id-Context-ID									ProtocolIE-ID ::= 3
id-RANAP-Message								ProtocolIE-ID ::= 4
id-IntraDomainNasNodeSelector					ProtocolIE-ID ::= 5
id-Establishment-Cause							ProtocolIE-ID ::= 6
id-CN-DomainIndicator							ProtocolIE-ID ::= 7
id-CSGMembershipStatus 							ProtocolIE-ID ::= 9

 
END
